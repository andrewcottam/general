FME workspace water_country_statistics_csv_to_postgresql_fields_ordered_correctly_21_03_2016.fmw

Parameters:
- DestDataset_POSTGRES = h05googleearthengine   # Destination PostgreSQL Dataset
- SourceDataset_CSV_3 = E:\cottaan\My Documents\Downloads\water_statistics_20160320.csv   # Source Comma Separated Value (CSV) File(s)

Readers:
- CSV_1: CSV from $(SourceDataset_CSV_3)

Writers:
- POSTGRES_1: POSTGRES to $(DestDataset_POSTGRES)

water_statistics_20160320 (reader CSV_1)
    attributes: system:index char(8), C01 number(31,15), C02 number(31,15), C03 number(31,15), C04 number(31,15), C05 number(31,15), C06 number(31,15), C07 number(31,15), C08 number(31,15), C09 number(31,15), C10 number(31,15), C11 number(31,15), C12 number(31,15), C13 number(31,15), C14 number(31,15), C15 number(22,14), C16 number(31,15), C17 number(31,15), C18 number(31,15), C19 number(31,15), C20 number(22,14), C21 number(31,15), C22 number(31,15), C23 number(31,15), C24 number(31,15), C25 number(31,15), C26 number(31,15), C27 number(31,15), C28 number(31,15), C29 number(31,15),
      C30 number(22,14), C31 number(31,15), C32 number(31,15), C33 number(31,15), C34 number(31,15), C35 number(31,15), C36 number(31,15), C37 number(31,15), C38 number(31,15), C39 number(31,15), C40 number(31,15), C41 number(31,15), C42 number(31,15), C43 number(31,15), C44 number(31,15), C45 number(31,15), C46 number(31,15), C47 number(31,15), C48 number(31,15), C49 number(31,15), C50 number(31,15), ISO char(4), NAME_0 char(45), .geo char(1)
    -> especies.water_statistics_raw_with_objectid (writer POSTGRES_1)
especies.water_statistics_raw_with_objectid (writer POSTGRES_1)
    attributes: name varchar(60), system_index varchar(20), objectid int4, iso varchar(20), c01 float8, c02 float8, c03 float8, c04 float8, c05 float8, c06 float8, c07 float8, c08 float8, c09 float8, c10 float8, c11 float8, c12 float8, c13 float8, c14 float8, c15 float8, c16 float8, c17 float8, c18 float8, c19 float8, c20 float8, c21 float8, c22 float8, c23 float8, c24 float8, c25 float8, c26 float8,
      c27 float8, c28 float8, c29 float8, c30 float8, c31 float8, c32 float8, c33 float8, c34 float8, c35 float8, c36 float8, c37 float8, c38 float8, c39 float8, c40 float8, c41 float8, c42 float8, c43 float8, c44 float8, c45 float8, c46 float8, c47 float8, c48 float8, c49 float8, c50 float8
