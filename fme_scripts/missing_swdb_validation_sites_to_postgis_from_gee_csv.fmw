FME workspace missing_swdb_validation_sites_to_postgis_from_gee_csv.fmw

Parameters:
- SourceDataset_CSV = E:\cottaan\My Documents\Downloads\feng_validation_points.csv   # Source Comma Separated Value (CSV) File(s)
- DestDataset_POSTGIS = h05googleearthengine   # Destination PostGIS Dataset

Readers:
- CSV_1: CSV from $(SourceDataset_CSV) in EPSG:4326

Writers:
- POSTGIS_1: POSTGIS to $(DestDataset_POSTGIS) in EPSG:4326

feng_validation_points (reader CSV_1)
    attributes: system:index char(9), id number(5,0), predicted_class char(10), sceneid char(22), sensor char(10), .geo char(69)
    -> especies.swdb_missing_validation_points (writer POSTGIS_1)
especies.swdb_missing_validation_points (writer POSTGIS_1)
    attributes: system:index varchar(9), id int4, predicted_class varchar(255), sceneid varchar(255), sensor varchar(10), _geo varchar(255), objectid int8, original_lng float8, original_lat float8, gee_lng float8, gee_lat float8, glc2000 text, scene_date timestamp, cloud_cover float4, sun_elevation float4, actual_class text, entry_date timestamp, username char(50), maskslope bool, maskndvi bool, masktemperature bool, maskbarerock bool, generation_date timestamp, waterclass char(20)
