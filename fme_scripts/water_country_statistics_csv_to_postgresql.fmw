FME workspace water_country_statistics_csv_to_postgresql.fmw

Parameters:
- SourceDataset_CSV = E:\cottaan\My Documents\Downloads\water_statistics (1).csv   # Source Comma Separated Value (CSV) File(s)
- DestDataset_POSTGRES = h05googleearthengine   # Destination PostgreSQL Dataset

Readers:
- CSV_1: CSV from $(SourceDataset_CSV)

Writers:
- POSTGRES_1: POSTGRES to $(DestDataset_POSTGRES)

water_statistics (1) (reader CSV_1)
    attributes: col0 char(13), col1 char(4), col2 char(18), col3 char(19), col4 char(17), col5 char(19), col6 char(18), col7 char(4), col8 char(19), col9 char(19), col10 char(19), col11 char(4), col12 char(17), col13 char(4), col14 char(18), col15 char(17), col16 char(19), col17 char(18), col18 char(18), col19 char(18), col20 char(19), col21 char(18), col22 char(4), col23 char(19), col24 char(4), col25 char(4), col26 char(19), col27 char(18), col28 char(18), col29 char(18),
      col30 char(4), col31 char(18), col32 char(19), col33 char(18), col34 char(18), col35 char(18), col36 char(18), col37 char(19), col38 char(18), col39 char(16), col40 char(19), col41 char(19), col42 char(19), col43 char(19), col44 char(19), col45 char(19), col46 char(4), col47 char(4), col48 char(18), col49 char(19), col50 char(18), col51 char(11), col52 char(327)
    -> especies.water_statistics_raw (writer POSTGRES_1)
especies.water_statistics_raw (writer POSTGRES_1)
    attributes: name varchar(60), iso varchar(20), c01 float8, c02 float8, c03 float8, c04 float8, c05 float8, c06 float8, c07 float8, c08 float8, c09 float8, c10 float8, c11 float8, c12 float8, c13 float8, c14 float8, c15 float8, c16 float8, c17 float8, c18 float8, c19 float8, c20 float8, c21 float8, c22 float8, c23 float8, c24 float8, c25 float8, c26 float8, c27 float8, c28 float8,
      c29 float8, c30 float8, c31 float8, c32 float8, c33 float8, c34 float8, c35 float8, c36 float8, c37 float8, c38 float8, c39 float8, c40 float8, c41 float8, c42 float8, c43 float8, c44 float8, c45 float8, c46 float8, c47 float8, c48 float8, c49 float8, c50 float8
