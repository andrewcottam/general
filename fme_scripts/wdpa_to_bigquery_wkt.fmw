FME workspace wdpa_to_bigquery_wkt.fmw

Parameters:
- SourceDataset_FILEGDB = E:\cottaan\Documents\ArcGIS\Datasets\wdpa\WDPA_Mar2018_Public\WDPA_Mar2018_Public.gdb   # Source Geodatabase
- DestDataset_CSV = E:\cottaan\Documents   # Destination CSV (Comma Separated Value) Folder

Readers:
- FILEGDB_1: FILEGDB from $(SourceDataset_FILEGDB)

Writers:
- CSV_1: CSV to $(DestDataset_CSV)

WDPA_point_Mar2018 (reader FILEGDB_1)
    attributes: OBJECTID objectid, WDPAID double, WDPA_PID text(52), PA_DEF text(20), NAME text(254), ORIG_NAME text(254), DESIG text(254), DESIG_ENG text(254), DESIG_TYPE text(20), IUCN_CAT text(20), INT_CRIT text(100), MARINE text(20), REP_M_AREA double, REP_AREA double, NO_TAKE text(50), NO_TK_AREA double, STATUS text(100), STATUS_YR int, GOV_TYPE text(254), OWN_TYPE text(254), MANG_AUTH text(254), MANG_PLAN text(254), VERIF text(20), METADATAID int, SUB_LOC text(100), ISO3 text(50), PARENT_ISO3 text(50)
    -> GeometryExtractor
GeometryExtractor
    ATTR = _geometry
    OGCVERSION = 1.1
    KIND_LONG = OGC Well Known Text
    REMOVE_GEOMETRY = No
    OGC_WKT_PRECISION_DISPLAY = Shortened 64-bit
    -> GeometryValidator
GeometryValidator
    ARC_ENDPOINT_TOLERANCE_MODE = Auto
    ORIENTATION_CHECK_DIR = Valid
    CHECK_HOLE_TOUCHING_POLYGON = No
    FLIP_APPEARANCES_CHOICE = Yes
    ANGULAR_TOLERANCE_CHOICE = Automatic
    SHELL_VALIDATION = SHELL_VALIDATION
    AREA_ORIENTATION = AREA_ORIENTATION
    SELF_INTERSECTING = SELF_INTERSECTING
    ISSUE_ATTR_NAME = _issues
    OGC_VERSION_CHOICE = 1.2.0
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = First Wins
    CONSECUTIVE_IDENTICAL_VERTICES_2D = CONSECUTIVE_IDENTICAL_VERTICES_2D
    OGC_VALID_CHECK = OGC_VALID_CHECK
    CHECK_AREA_CHOICE = No
    THICKNESS_TOLERANCE_CHOICE = Automatic
    REPAIR = Yes
    NULL_REMOVAL = NULL_REMOVAL
    NAN_REMOVAL = NAN_REMOVAL
    CONNECT_Z_MODE_SI = First Wins
    OGC_SIMPLE_CHECK = OGC_SIMPLE_CHECK
    PLANAR_SURFACE = PLANAR_SURFACE
    PRESETS = All
    MISSING_TEXTURE_COORDINATES = MISSING_TEXTURE_COORDINATES
    SUMMARY = Detailed
    TYPE_REPAIR = TYPE_REPAIR
    DUP_COORDS_CHECK_Z = Yes
    MISSING_VERTEX_NORMALS = MISSING_VERTEX_NORMALS
    SOLID_VOID_REPAIR = SOLID_VOID_REPAIR
    PASSED -> wdpa_points (writer CSV_1)
wdpa_points (writer CSV_1)
    attributes: OBJECTID int, WDPAID float, WDPA_PID text, PA_DEF text, NAME text, ORIG_NAME text, DESIG text, DESIG_ENG text, DESIG_TYPE text, IUCN_CAT text, INT_CRIT text, MARINE text, REP_M_AREA float, REP_AREA float, NO_TAKE text, NO_TK_AREA float, STATUS text, STATUS_YR int, GOV_TYPE text, OWN_TYPE text, MANG_AUTH text, MANG_PLAN text, VERIF text, METADATAID int, SUB_LOC text, ISO3 text, PARENT_ISO3 text, geometry auto
WDPA_poly_Mar2018 (reader FILEGDB_1)
    attributes: OBJECTID objectid, WDPAID double, WDPA_PID text(50), PA_DEF text(20), NAME text(254), ORIG_NAME text(254), DESIG text(254), DESIG_ENG text(254), DESIG_TYPE text(20), IUCN_CAT text(20), INT_CRIT text(100), MARINE text(20), REP_M_AREA double, GIS_M_AREA double, REP_AREA double, GIS_AREA double, NO_TAKE text(50), NO_TK_AREA double, STATUS text(100), STATUS_YR int, GOV_TYPE text(254), OWN_TYPE text(254), MANG_AUTH text(254), MANG_PLAN text(254), VERIF text(20), METADATAID int, SUB_LOC text(100), PARENT_ISO3 text(50), ISO3 text(50), Shape_Length double,
      Shape_Area double
    -> GeometryExtractor_2
GeometryExtractor_2
    ATTR = _geometry
    OGCVERSION = 1.1
    KIND_LONG = OGC Well Known Text
    REMOVE_GEOMETRY = No
    OGC_WKT_PRECISION_DISPLAY = Shortened 64-bit
    -> GeometryValidator_2
GeometryValidator_2
    ARC_ENDPOINT_TOLERANCE_MODE = Auto
    ORIENTATION_CHECK_DIR = Valid
    CHECK_HOLE_TOUCHING_POLYGON = No
    FLIP_APPEARANCES_CHOICE = Yes
    ANGULAR_TOLERANCE_CHOICE = Automatic
    SHELL_VALIDATION = SHELL_VALIDATION
    AREA_ORIENTATION = AREA_ORIENTATION
    SELF_INTERSECTING = SELF_INTERSECTING
    ISSUE_ATTR_NAME = _issues
    OGC_VERSION_CHOICE = 1.2.0
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = First Wins
    CONSECUTIVE_IDENTICAL_VERTICES_2D = CONSECUTIVE_IDENTICAL_VERTICES_2D
    OGC_VALID_CHECK = OGC_VALID_CHECK
    CHECK_AREA_CHOICE = No
    THICKNESS_TOLERANCE_CHOICE = Automatic
    REPAIR = Yes
    NULL_REMOVAL = NULL_REMOVAL
    NAN_REMOVAL = NAN_REMOVAL
    CONNECT_Z_MODE_SI = First Wins
    OGC_SIMPLE_CHECK = OGC_SIMPLE_CHECK
    PLANAR_SURFACE = PLANAR_SURFACE
    PRESETS = All
    MISSING_TEXTURE_COORDINATES = MISSING_TEXTURE_COORDINATES
    SUMMARY = Detailed
    TYPE_REPAIR = TYPE_REPAIR
    DUP_COORDS_CHECK_Z = Yes
    MISSING_VERTEX_NORMALS = MISSING_VERTEX_NORMALS
    SOLID_VOID_REPAIR = SOLID_VOID_REPAIR
    PASSED -> wdpa_polygons (writer CSV_1)
wdpa_polygons (writer CSV_1)
    attributes: OBJECTID int, WDPAID float, WDPA_PID text, PA_DEF text, NAME text, ORIG_NAME text, DESIG text, DESIG_ENG text, DESIG_TYPE text, IUCN_CAT text, INT_CRIT text, MARINE text, REP_M_AREA float, GIS_M_AREA float, REP_AREA float, GIS_AREA float, NO_TAKE text, NO_TK_AREA float, STATUS text, STATUS_YR int, GOV_TYPE text, OWN_TYPE text, MANG_AUTH text, MANG_PLAN text, VERIF text, METADATAID int, SUB_LOC text, PARENT_ISO3 text, ISO3 text, Shape_Length float,
      Shape_Area float, geometry auto
