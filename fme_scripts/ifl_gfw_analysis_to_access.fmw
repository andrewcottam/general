FME workspace ifl_gfw_analysis_to_access.fmw

Parameters:
- SourceDataset_CSV = e:\cottaan\Downloads\IFL temporal analysis using Global Forest Watch.csv   # Source CSV (Comma Separated Value) File(s)
- DestDataset_MDB_ADO = E:\cottaan\Documents\Database1.accdb   # Destination Microsoft Access Database File

Readers:
- CSV_1: CSV from $(SourceDataset_CSV)

Writers:
- MDB_ADO_1: MDB_ADO to $(DestDataset_MDB_ADO)

CSV (reader CSV_1)
    attributes: system:index char(21), 2001 number(31,15), 2002 number(31,15), 2003 number(31,15), 2004 number(31,15), 2005 number(31,15), 2006 number(31,15), 2007 number(31,15), 2008 number(31,15), 2009 number(31,15), 2010 number(31,15), 2011 number(31,15), 2012 number(31,15), 2013 number(31,15), 2014 number(31,15), 2015 number(31,15), 2016 number(31,15), AREA_HA number(31,15), FID_Intact number(5,0), FID_jrc_ga number(4,0), IFL_ID char(10), Shape_Area number(31,15), Shape_Leng number(17,13), area_km2 number(3,1), id_country number(4,0), id_object number(4,0), iso2 char(6), iso3 char(8), name_iso31 char(35), orig_ogc_f number(4,0),
      original_d char(66), original_n char(41), source char(5), source_cod char(8), sovereig_1 char(6), sovereig_2 char(8), sovereign_ char(8), status char(9), un_m49 char(8), .geo char(17735527)
    -> ifl_gfw analysis (writer MDB_ADO_1)
ifl_gfw analysis (writer MDB_ADO_1)
    attributes: system_index text(21), 2001 decimal(31,15), 2002 decimal(31,15), 2003 decimal(31,15), 2004 decimal(31,15), 2005 decimal(31,15), 2006 decimal(31,15), 2007 decimal(31,15), 2008 decimal(31,15), 2009 decimal(31,15), 2010 decimal(31,15), 2011 decimal(31,15), 2012 decimal(31,15), 2013 decimal(31,15), 2014 decimal(31,15), 2015 decimal(31,15), 2016 decimal(31,15), AREA_HA decimal(31,15), FID_Intact decimal(5,0), FID_jrc_ga decimal(4,0), IFL_ID text(10), Shape_Area decimal(31,15), Shape_Leng decimal(17,13), iso3 text(8)
