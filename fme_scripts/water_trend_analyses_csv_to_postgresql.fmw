FME workspace water_trend_analyses_csv_to_postgresql.fmw

Parameters:
- SourceDataset_CSV = E:\cottaan\My Documents\Downloads\Water_trend-2016-04-26\country_trend_analysis.csv   # Source Comma Separated Value (CSV) File(s)
- DestDataset_POSTGRES = h05googleearthengine   # Destination PostgreSQL Dataset

Readers:
- CSV_1: CSV from $(SourceDataset_CSV)

Writers:
- POSTGRES_1: POSTGRES to $(DestDataset_POSTGRES)

country_trend_analysis (reader CSV_1)
    attributes: iso char(4), name_0 char(45), objectid number(6,0), maybePermanent number(26,20), maybeSeasonal number(25,20), permanent number(26,20), seasonal number(25,20), year number(5,0)
    -> especies.water_trend_analysis_raw (writer POSTGRES_1)
especies.water_trend_analysis_raw (writer POSTGRES_1)
    attributes: iso varchar(4), name_0 varchar(45), objectid int4, maybepermanent float8, maybeseasonal float8, permanent float8, seasonal float8, _year int4
