FME workspace validation_points_from_csv_to_postgresql.fmw

Parameters:
- SourceDataset_CSV = E:\cottaan\My Documents\ArcGIS\Google Earth Engine Downloads\final_validation_sites.csv   # Source Comma Separated Value (CSV) File(s)
- DestDataset_POSTGRES = h05googleearthengine   # Destination PostgreSQL Dataset

Readers:
- CSV_1: CSV from $(SourceDataset_CSV)

Writers:
- POSTGRES_1: POSTGRES to $(DestDataset_POSTGRES)

final_validation_sites (reader CSV_1)
    attributes: oid number(10,0), sceneid char(42), sensor char(10), predicted_class char(10), actual_class char(10), latitude number(12,7), longitude number(11,7)
    -> especies.final_validation_results (writer POSTGRES_1)
especies.final_validation_results (writer POSTGRES_1)
    attributes: _oid float8, sceneid char(42), sensor char(10), predicted_class char(10), actual_class char(10), latitude float8, longitude float8
