FME workspace csv_to_postgresql_all_l7_missing_water_pixels.fmw

Parameters:
- SourceDataset_CSV = E:\cottaan\My Documents\ArcGIS\Google Earth Engine Downloads\ommissionl7_pixel_values.csv   # Source Comma Separated Value (CSV) File(s)
- DestDataset_POSTGIS = h05googleearthengine   # Destination PostGIS Dataset

Readers:
- CSV_1: CSV from $(SourceDataset_CSV)

Writers:
- POSTGIS_1: POSTGIS to $(DestDataset_POSTGIS) in EPSG:4326

ommissionl7_pixel_values (reader CSV_1)
    attributes: system:index number(4,0), B1 number(31,17), B2 number(31,18), B3 number(20,18), B4 number(20,18), B5 number(31,19), B6_VCID_1 number(18,14), B6_VCID_2 number(18,14), B7 number(31,19), B8 number(20,18), sceneid char(22), longitude number(14,9), latitude number(31,15)
    -> 2DPointReplacer
2DPointReplacer
    YVALATTR = @Value(latitude)
    XVALATTR = @Value(longitude)
    POINT -> especies.ommissionl7_pixel_values (writer POSTGIS_1)
especies.ommissionl7_pixel_values (writer POSTGIS_1)
    attributes: objectid int2, b1 float8, b2 float8, b3 float8, b4 float8, b5 float8, b6_vcid_1 float8, b6_vcid_2 float8, b7 float8, b8 float8, sceneid text
