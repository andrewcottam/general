FME workspace water_country_statistics_csv_to_access.fmw

Parameters:
- SourceDataset_CSV = E:\cottaan\My Documents\Downloads\water_statistics_20160728_v2.csv   # Source CSV (Comma Separated Value) File(s)
- DestDataset_MDB_ADO = E:\cottaan\My Documents\global_water_statistics.accdb   # Destination Microsoft Access Database File

Readers:
- CSV_1: CSV from $(SourceDataset_CSV)

Writers:
- MDB_ADO_1: MDB_ADO to $(DestDataset_MDB_ADO)

CSV (reader CSV_1)
    attributes: system:index char(8), C01 number(31,15), C02 number(31,15), C03 number(31,15), C04 number(31,15), C05 number(21,13), C06 number(31,15), C07 number(31,15), C08 number(31,15), C09 number(31,15), C10 number(31,15), C11 number(31,15), C12 number(31,15), C13 number(21,13), C14 number(21,13), C15 number(21,13), C16 number(31,15), C17 number(31,15), C18 number(31,15), C19 number(31,15), C20 number(19,13), C21 number(31,15), C22 number(31,15), C23 number(31,15), C24 number(31,15), C25 number(21,13), C26 number(31,15), C27 number(31,15), C28 number(31,15), C29 number(31,15),
      C30 number(20,13), C31 number(31,15), C32 number(31,15), C33 number(31,15), C34 number(31,15), C35 number(31,15), C36 number(31,15), C37 number(31,15), C38 number(31,15), C39 number(31,15), C40 number(31,15), C41 number(31,15), C42 number(31,15), C43 number(31,15), C44 number(31,15), C45 number(31,15), C46 number(31,15), C47 number(31,15), C48 number(31,15), C49 number(31,15), C50 number(21,13), ISO char(4), NAME_0 char(15), .geo char(1)
    -> CSV (writer MDB_ADO_1)
CSV (writer MDB_ADO_1)
    attributes: system_index text(8), NAME_0 text(15), C01 decimal(31,15), C02 decimal(31,15), C03 decimal(31,15), C04 decimal(31,15), C05 decimal(21,13), C06 decimal(31,15), C07 decimal(31,15), C08 decimal(31,15), C09 decimal(31,15), C10 decimal(31,15), C11 decimal(31,15), C12 decimal(31,15), C13 decimal(21,13), C14 decimal(21,13), C15 decimal(21,13), C16 decimal(31,15), C17 decimal(31,15), C18 decimal(31,15), C19 decimal(31,15), C20 decimal(19,13), C21 decimal(31,15), C22 decimal(31,15), C23 decimal(31,15), C24 decimal(31,15), C25 decimal(21,13), C26 decimal(31,15), C27 decimal(31,15), C28 decimal(31,15),
      C29 decimal(31,15), C30 decimal(20,13), C31 decimal(31,15), C32 decimal(31,15), C33 decimal(31,15), C34 decimal(31,15), C35 decimal(31,15), C36 decimal(31,15), C37 decimal(31,15), C38 decimal(31,15), C39 decimal(31,15), C40 decimal(31,15), C41 decimal(31,15), C42 decimal(31,15), C43 decimal(31,15), C44 decimal(31,15), C45 decimal(31,15), C46 decimal(31,15), C47 decimal(31,15), C48 decimal(31,15), C49 decimal(31,15), C50 decimal(21,13), ISO text(4)
