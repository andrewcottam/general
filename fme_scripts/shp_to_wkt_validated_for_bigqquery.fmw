FME workspace shp_to_wkt_validated_for_bigqquery.fmw

Parameters:
- SourceDataset_ESRISHAPE = E:\cottaan\Documents\ArcGIS\Datasets\Intact Forest Landscapes\IFL_2013\ifl_2013_pacific.shp   # Source Esri Shapefile(s)
- DestDataset_CSV = E:\cottaan\Documents   # Destination CSV (Comma Separated Value) Folder

Readers:
- ESRISHAPE_1: ESRISHAPE from $(SourceDataset_ESRISHAPE)

Writers:
- CSV_1: CSV to $(DestDataset_CSV)

ifl_2013_pacific (reader ESRISHAPE_1)
    attributes: IFL_ID char(16), AREA_HA double
    -> GeometryExtractor
GeometryExtractor
    OGC_WKT_PRECISION_DISPLAY = Shortened 64-bit
    REMOVE_GEOMETRY = No
    KIND_LONG = OGC Well Known Text
    ATTR = geometry
    OGCVERSION = 1.2
    -> GeometryValidator
GeometryValidator
    THICKNESS_TOLERANCE_CHOICE = Automatic
    MISSING_TEXTURE_COORDINATES = MISSING_TEXTURE_COORDINATES
    DUP_COORDS_CHECK_Z = Yes
    SUMMARY = Detailed
    SOLID_VOID_REPAIR = SOLID_VOID_REPAIR
    OGC_VALID_CHECK = OGC_VALID_CHECK
    CONNECT_Z_MODE_TR = First Wins
    ISSUE_ATTR_NAME = _issues
    OGC_VERSION_CHOICE = 1.2.0
    MISSING_VERTEX_NORMALS = MISSING_VERTEX_NORMALS
    CHECK_HOLE_TOUCHING_POLYGON = No
    OGC_SIMPLE_CHECK = OGC_SIMPLE_CHECK
    TYPE_REPAIR = TYPE_REPAIR
    ORIENTATION_CHECK_DIR = Valid
    NULL_REMOVAL = NULL_REMOVAL
    CHECK_AREA_CHOICE = No
    NAN_REMOVAL = NAN_REMOVAL
    CONSECUTIVE_IDENTICAL_VERTICES_2D = CONSECUTIVE_IDENTICAL_VERTICES_2D
    CONNECT_Z_MODE_SI = First Wins
    AREA_ORIENTATION = AREA_ORIENTATION
    PLANAR_SURFACE = PLANAR_SURFACE
    ARC_ENDPOINT_TOLERANCE_MODE = Auto
    FLIP_APPEARANCES_CHOICE = Yes
    ANGULAR_TOLERANCE_CHOICE = Automatic
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SELF_INTERSECTING = SELF_INTERSECTING
    SHELL_VALIDATION = SHELL_VALIDATION
    REPAIR = Yes
    PRESETS = All
    PASSED -> ifl_2013_pacific (writer CSV_1)
ifl_2013_pacific (writer CSV_1)
    attributes: IFL_ID char(16), AREA_HA float, geometry auto
