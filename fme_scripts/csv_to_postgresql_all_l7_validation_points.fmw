FME workspace csv_to_postgresql_all_l7_validation_points.fmw

Parameters:
- SourceDataset_CSV = E:\cottaan\My Documents\ArcGIS\Google Earth Engine Downloads\validation_sites_ommission_l7.csv   # Source Comma Separated Value (CSV) File(s)
- DestDataset_POSTGRES = h05googleearthengine   # Destination PostgreSQL Dataset

Readers:
- CSV_1: CSV from $(SourceDataset_CSV)

Writers:
- POSTGRES_1: POSTGRES to $(DestDataset_POSTGRES)

validation_sites_ommission_l7 (reader CSV_1)
    attributes: objectID number(7,0), sceneid char(42), longitude number(11,6), latitude number(10,6), water number(3,0)
    -> especies.swdb_validated_sites_l7 (writer POSTGRES_1)
especies.swdb_validated_sites_l7 (writer POSTGRES_1)
    attributes: objectid int4, sceneid varchar(42), longitude float8, latitude float8, water int2
