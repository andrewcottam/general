FME workspace validation_points_from_csv_to_postgresql_16_03_2016.fmw

Parameters:
- SourceDataset_CSV = E:\cottaan\My Documents\ArcGIS\Google Earth Engine Downloads\final_validation_sites_16_mar.csv   # Source Comma Separated Value (CSV) File(s)
- DestDataset_POSTGRES = h05googleearthengine   # Destination PostgreSQL Dataset

Readers:
- CSV_1: CSV from $(SourceDataset_CSV)

Writers:
- POSTGRES_1: POSTGRES to $(DestDataset_POSTGRES)

final_validation_sites_16_mar (reader CSV_1)
    attributes: oid number(10,0), sceneid char(42), sensor char(10), predicted_class char(24), actual_class char(10), latitude number(12,7), longitude number(31,15)
    -> especies.validation_results_16_03_2016 (writer POSTGRES_1)
especies.validation_results_16_03_2016 (writer POSTGRES_1)
    attributes: _oid float8, sceneid varchar(42), sensor varchar(10), predicted_class varchar(24), actual_class varchar(10), latitude float8, longitude float8
