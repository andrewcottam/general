FME workspace l5_l7_validation_points_to_postgresql.fmw

Parameters:
- SourceDataset_CSV = E:\cottaan\My Documents\ArcGIS\Google Earth Engine Downloads\l5_l7_validation_sites.csv   # Source Comma Separated Value (CSV) File(s)
- DestDataset_POSTGRES = H05-googleearthengine   # Destination PostgreSQL Dataset

Readers:
- CSV_1: CSV from $(SourceDataset_CSV)

Writers:
- POSTGRES_1: POSTGRES to $(DestDataset_POSTGRES)

l5_l7_validation_sites (reader CSV_1)
    attributes: col0 char(9), col1 char(28), col2 char(22), col3 char(21), col4 char(20), col5 char(7), col6 char(11), col7 char(9), col8 char(9), col9 char(13)
    -> especies.l5_l7_validation_sites (writer POSTGRES_1)
especies.l5_l7_validation_sites (writer POSTGRES_1)
    attributes: objectid varchar(9), filename varchar(50), sceneid varchar(22), longitude varchar(21), latitude varchar(20), sensor varchar(7), water_class varchar(11), lon_grid varchar(9), lat_grid varchar(9), grid varchar(13)
