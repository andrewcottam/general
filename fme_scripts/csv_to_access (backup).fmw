FME workspace csv_to_access (backup).fmw

Parameters:
- SourceDataset_CSV = E:\cottaan\My Documents\Downloads\waterstats.csv   # Source Comma Separated Value (CSV) File(s)
- DestDataset_MDB_ADO = E:\cottaan\My Documents\h05googleearthengine_client.accdb   # Destination Microsoft Access Database File

Readers:
- CSV_1: CSV from $(SourceDataset_CSV)

Writers:
- MDB_ADO_1: MDB_ADO to $(DestDataset_MDB_ADO)

waterstats (reader CSV_1)
    attributes: system:index number(5,0), C01 number(31,15), C02 number(31,15), C03 number(31,15), C04 number(21,13), C05 number(21,14), C06 number(31,15), C07 number(31,15), C08 number(31,15), C09 number(31,15), C10 number(31,15), C11 number(22,14), C12 number(22,14), C13 number(22,14), C14 number(31,15), C15 number(21,13), C16 number(31,15), C17 number(31,15), C18 number(22,14), C19 number(21,14), C20 number(20,14), C21 number(31,15), C22 number(31,15), C23 number(31,15), C24 number(31,15), C25 number(22,14), C26 number(31,15), C27 number(31,15), C28 number(22,14), C29 number(22,14),
      C30 number(21,14), C31 number(31,15), C32 number(31,15), C33 number(31,15), C34 number(31,15), C35 number(22,14), C36 number(22,14), C37 number(31,15), C38 number(31,15), C39 number(31,15), C40 number(21,14), C41 number(31,15), C42 number(31,15), C43 number(31,15), C44 number(31,15), C45 number(22,14), C46 number(31,15), C47 number(31,15), C48 number(22,14), C49 number(31,15), C50 number(21,13), ISO3 char(8), WDPAID number(31,15), description char(1), name char(1), split number(3,1), split2 number(3,1), .geo char(57)
    -> waterstats (writer MDB_ADO_1)
waterstats (writer MDB_ADO_1)
    attributes: system_index decimal(5,0), C01 decimal(31,15), C02 decimal(31,15), C03 decimal(31,15), C04 decimal(21,13), C05 decimal(21,14), C06 decimal(31,15), C07 decimal(31,15), C08 decimal(31,15), C09 decimal(31,15), C10 decimal(31,15), C11 decimal(22,14), C12 decimal(22,14), C13 decimal(22,14), C14 decimal(31,15), C15 decimal(21,13), C16 decimal(31,15), C17 decimal(31,15), C18 decimal(22,14), C19 decimal(21,14), C20 decimal(20,14), C21 decimal(31,15), C22 decimal(31,15), C23 decimal(31,15), C24 decimal(31,15), C25 decimal(22,14), C26 decimal(31,15), C27 decimal(31,15), C28 decimal(22,14), C29 decimal(22,14),
      C30 decimal(21,14), C31 decimal(31,15), C32 decimal(31,15), C33 decimal(31,15), C34 decimal(31,15), C35 decimal(22,14), C36 decimal(22,14), C37 decimal(31,15), C38 decimal(31,15), C39 decimal(31,15), C40 decimal(21,14), C41 decimal(31,15), C42 decimal(31,15), C43 decimal(31,15), C44 decimal(31,15), C45 decimal(22,14), C46 decimal(31,15), C47 decimal(31,15), C48 decimal(22,14), C49 decimal(31,15), C50 decimal(21,13), ISO3 text(8), WDPAID long, description text(1), name text(1), split decimal(3,1), split2 decimal(3,1)
