FME workspace postgresql_to_kml_all_validation_points.fmw

Parameters:
- SourceDataset_POSTGRES = H05-googleearthengine   # Source PostgreSQL Dataset
- DestDataset_OGCKML = E:\cottaan\My Documents\ArcGIS\Google Earth Engine Downloads\all_validation_points.kml   # Destination Google Earth KML File

Readers:
- POSTGRES_1: POSTGRES from $(SourceDataset_POSTGRES)

Writers:
- OGCKML_1: OGCKML to $(DestDataset_OGCKML) in EPSG:4326

especies.validation_points (reader POSTGRES_1)
    attributes: objectid int4, longitude float8, latitude float8
    -> 2DPointReplacer
2DPointReplacer
    YVALATTR = @Value(latitude)
    XVALATTR = @Value(longitude)
    POINT -> validation_points (writer OGCKML_1)
validation_points (writer OGCKML_1)
    attributes: objectid kml_int32
