FME workspace feng_validation_sites_to_postgis.fmw

Parameters:
- SourceDataset_FILEGDB = E:\cottaan\My Documents\ArcGIS\Google Earth Engine Downloads\sampleValidationSites.gdb   # *.gdb Source Geodatabase
- DestDataset_POSTGIS = h05googleearthengine   # Destination PostGIS Dataset

Readers:
- FILEGDB_1: FILEGDB from $(SourceDataset_FILEGDB) in EPSG:4326

Writers:
- POSTGIS_1: POSTGIS to $(DestDataset_POSTGIS) in EPSG:4326

Feng_Validation_Points (reader FILEGDB_1)
    attributes: OBJECTID objectid, Field1 double, Field2 double, land_sea smallint, coastal smallint, WaterClass text(50), rnd int
    -> especies.feng_validated_sites (writer POSTGIS_1)
especies.feng_validated_sites (writer POSTGIS_1)
    attributes: objectid int4, lng float8, lat float8, land_sea int2, coastal int2, waterclass varchar(50), rnd int4
