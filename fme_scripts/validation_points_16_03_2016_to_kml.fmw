FME workspace validation_points_16_03_2016_to_kml.fmw

Parameters:
- SourceDataset_POSTGRES = h05googleearthengine   # Source PostgreSQL Dataset
- DestDataset_OGCKML = E:\cottaan\My Documents\ArcGIS\Google Earth Engine Downloads\validation_results_16_03_2016.kml   # Destination Google Earth KML File

Readers:
- POSTGRES_1: POSTGRES from $(SourceDataset_POSTGRES) in EPSG:4326

Writers:
- OGCKML_1: OGCKML to $(DestDataset_OGCKML) in EPSG:4326

especies.validation_results_16_03_2016 (reader POSTGRES_1)
    attributes: _oid float8, sceneid varchar(42),PRIKEY, sensor varchar(10), predicted_class varchar(24), actual_class varchar(10), latitude float8, longitude float8, validation_type text
    -> 2DPointReplacer
2DPointReplacer
    YVALATTR = @Value(latitude)
    XVALATTR = @Value(longitude)
    POINT -> especies.validation_results_16_03_2016 (writer OGCKML_1)
especies.validation_results_16_03_2016 (writer OGCKML_1)
    attributes: _oid kml_real64, sceneid kml_char(42), sensor kml_char(10), predicted_class kml_char(24), actual_class kml_char(10), latitude kml_real64, longitude kml_real64, validation_type kml_char(255)
