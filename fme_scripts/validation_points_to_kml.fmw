FME workspace validation_points_to_kml.fmw

Parameters:
- SourceDataset_POSTGRES_3 = h05googleearthengine   # Source PostgreSQL Dataset
- DestDataset_OGCKML_3 = E:\cottaan\My Documents\ArcGIS\Google Earth Engine Downloads\validation_points.kml   # Destination Google Earth KML File

Readers:
- POSTGRES_2: POSTGRES from $(SourceDataset_POSTGRES_3) in EPSG:4326

Writers:
- OGCKML_2: OGCKML to $(DestDataset_OGCKML_3)

especies.validation_results_withoid (reader POSTGRES_2)
    attributes: oid oid, sensor text, sceneid varchar(255), longitude float8, latitude float8, predicted_class text, actual_class text
    -> 2DPointReplacer_2
2DPointReplacer_2
    YVALATTR = @Value(latitude)
    XVALATTR = @Value(longitude)
    POINT -> validation_points (writer OGCKML_2)
validation_points (writer OGCKML_2)
    attributes: oid kml_char(20), longitude kml_char(20), latitude kml_char(20), sensor kml_char(20), sceneid kml_char(20), predicted_class kml_char(20), actual_class kml_char(20)
