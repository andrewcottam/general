FME workspace tmp.fmw

Parameters:
- DestDataset_POSTGRES = h05googleearthengine   # Destination PostgreSQL Dataset
- SourceDataset_CSV = E:\cottaan\My Documents\Downloads\tibetan_plateau_water_statistics.csv   # Source Comma Separated Value (CSV) File(s)

Readers:
- CSV_1: CSV from $(SourceDataset_CSV)

Writers:
- POSTGRES_1: POSTGRES to $(DestDataset_POSTGRES)

tibetan_plateau_water_statistics (reader CSV_1)
    attributes: Name char(16), C01 number(10,0), C02 number(10,0), C03 number(10,0), C04 number(9,0), C05 number(8,0), C06 number(11,0), C07 number(10,0), C08 number(11,0), C09 number(10,0), C10 number(9,0), C11 number(10,0), C12 number(10,0), C13 number(9,0), C14 number(9,0), C15 number(8,0), C16 number(10,0), C17 number(10,0), C18 number(9,0), C19 number(8,0), C20 number(7,0), C21 number(10,0), C22 number(11,0), C23 number(10,0), C24 number(10,0), C25 number(8,0), C26 number(12,0), C27 number(11,0), C28 number(10,0), C29 number(9,0),
      C30 number(8,0), C31 number(10,0), C32 number(10,0), C33 number(10,0), C34 number(10,0), C35 number(9,0), C36 number(10,0), C37 number(10,0), C38 number(9,0), C39 number(9,0), C40 number(8,0), C41 number(10,0), C42 number(11,0), C43 number(11,0), C44 number(10,0), C45 number(9,0), C46 number(11,0), C47 number(11,0), C48 number(11,0), C49 number(10,0), C50 number(9,0), col51 char(1), col52 char(1)
    -> especies.water_statistics_raw_tibet (writer POSTGRES_1)
especies.water_statistics_raw_tibet (writer POSTGRES_1)
    attributes: name varchar(60), iso varchar(20), c01 float8, c02 float8, c03 float8, c04 float8, c05 float8, c06 float8, c07 float8, c08 float8, c09 float8, c10 float8, c11 float8, c12 float8, c13 float8, c14 float8, c15 float8, c16 float8, c17 float8, c18 float8, c19 float8, c20 float8, c21 float8, c22 float8, c23 float8, c24 float8, c25 float8, c26 float8, c27 float8, c28 float8,
      c29 float8, c30 float8, c31 float8, c32 float8, c33 float8, c34 float8, c35 float8, c36 float8, c37 float8, c38 float8, c39 float8, c40 float8, c41 float8, c42 float8, c43 float8, c44 float8, c45 float8, c46 float8, c47 float8, c48 float8, c49 float8, c50 float8
